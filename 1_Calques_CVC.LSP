;;; Gestion des calques CVC 07.11.2016 ;;;
;;; - Variable dans le fichier 0_config

;;; chargement des variables
(load "0_Config")

;;; routine fr:rt-syst-ventil-or-hydro						
;;; retourne si le nom du système et un système de ventilation ou d'hydrolique	
;;; argument: str-syst "nom du système" 					

(defun fr:rt-syst-ventil-or-hydro (str-syst / type-syst)
  (cond	((vl-position
	   0
	   (mapcar '(lambda (x) (vl-position str-syst x))
		   cvc-syst-ventil
	   )
	 )
	 (setq type-syst "Ventilation")
	)
	((vl-position
	   0
	   (mapcar '(lambda (x) (vl-position str-syst x))
		   cvc-syst-hydro
	   )
	 )
	 (setq type-syst "Hydraulique")
	)
  )
  type-syst
)


;;; routine fr:ReadDesignCalqueGC										;;;
;;;														;;;
;;; argument: 	entitée sous forme <Nom d'entité: ID> (setq x (car(entsel)))					;;;
;;;		ou nom du calque en chaine de caractère								;;;
;;; Si pos Nil Retourne une liste sous le format ((Systeme Designation)(Type Designation)(Element Designation))	;;;
;;;		Pos   	0 pour un système 									;;;
;;; 			1 pour un type de système								;;;
;;; 			2 pour un élément de système								;;;

(defun fr:ReadDesignCalqueGC (x			pos		  /
			      layname		lst_layname	  design_lst_layname
			      design_lst_lst_layname
			     )
  (or (and (equal (type x) 'ENAME)
	   (setq layname (vla-get-layer (vlax-ename->vla-object x)))
      ) ;_ and
      (and (equal (type x) 'str)
	   (setq layname x)
      ) ;_ and
  ) ;_ or
  (c:setq lst_layname (gc:str2lst layname " "))
  (setq	design_lst_layname
	 (reverse
	   (cdr (reverse (cdr (member "-" lst_layname))))
	 ) ;_ reverse
  ) ;_ setq
  (setq	design_lst_lst_layname
	 (list (list nil nil)
	       (list nil nil)
	       (list nil nil)
	 ) ;_ list
  ) ;_ setq
  (foreach y design_lst_layname
    (setq design_lst_lst_layname
	   (gc:SubstAt
	     (if (wcmatch y "*_*")
	       (gc:str2lst y "_")
	       (list y nil)
	     ) ;_ if
	     (fr:PositionDesignCalque y)
	     design_lst_lst_layname
	   ) ;_ gc:SubstAt
    ) ;_ setq
  ) ;_ foreach
  (if pos (nth pos design_lst_lst_layname)
      design_lst_lst_layname
  ) ;_ or
)					;defun

;;; routine fr:PositionDesignCalque			
;;; Retourne:						
;;; 0 pour un système 					
;;; 1 pour un type de système				
;;; 2 pour un élément de système			
;;; nil ne fait pas partie d'un système 		
;;; Argument une chaine de caractère			

(defun fr:PositionDesignCalque (x / n)
  (setq	str (fr:ReadDesign1 x nil)
	n   nil
  )
  (or
    (foreach y cvc-syst-ventil
      (and (member str y) (setq n 0))
      n
    )
    (foreach y cvc-syst-hydro
      (and (member str y) (setFq n 0))
      n
    )
    (foreach y cvc-type-syst-ventil
      (and (member str y) (setq n 1))
      n
    )
    (foreach y cvc-type-syst-ventil
      (and (member str y) (setq n 1))
      n
    )
    (foreach y cvc-type-syst-hydro
      (and (member str y) (setq n 1))
      n
    )
    (foreach y cvc-element-syst
      (and (member str y) (setq n 2))
      n
    )
    (setq n nil)
  )
  n
)


;;; routine fr:ReadDesign1				
;;; Retourne la Désignation1 sans la désignation2	
;;; nb T retourne le système avec le numero		
;;; nb nil retourne le système sans le numero		

(defun fr:ReadDesign1 (x nb / nb)
  (if (listp x)
    (if	(car x)
      (setq x (car x))
      (setq x nil)
    ) ;_ if
    (and (wcmatch x "*_*") (progn (setq x (car (gc:str2lst x "_")))))
  ) ;_ if
  (and x (not nb) (distof (substr x (strlen x))) (setq x (substr x 1 (- (strlen x) 2))))
  x
) ;_ defun

;;; routine fr:ReadDesign2				
;;; Retourne la Désignation2 sans la désignation1	
;;; Retourne nil si pas de désignation 2		

(defun fr:ReadDesign2 (x / nb)
  (if (listp x)
    (setq x (cadr x))
    (or
    (and (wcmatch x "*_*")(setq x (cadr (gc:str2lst x "_"))))
    (setq x nil))
  ) ;_ if
  x
) ;_ defun

;;; routine fr:ReadAllDesign2							;;;
;;; Retourne une liste avec toutes les désignation utilisé 			;;;
;;; Retourne nil si pas de désignation 2					;;;
;;;										;;;
;;; Argument: 	str-des1 	chaine de caractère du système scécifique	;;;
;;; 				* pour tous les système du meme genre		;;;
;;; 				T pour tous les système 			;;;
;;;										;;;
;;;		Pos   		0 pour un système 				;;;
;;; 				1 pour un type de système			;;;
;;; 				2 pour un élément de système			;;;
;;;				T Pour tout					;;;


(defun fr:ReadAllDesign2 (str-des1 pos / lst_design2)
  (cond	(equal pos T)
    	((not pos)(setq pos T))
    	((< pos 0)(setq pos T))
	((> pos 2)(setq pos T))
  )   
  (vlax-for l *layers*
    (or	(not (fr:rt-veriflay (setq layname (vla-get-name l))))
	(and (equal str-des1 T)
	     (progn
	       (if (equal pos T)
		 (foreach x (fr:ReadDesignCalqueGC layname nil)
		   (and	(fr:ReadDesign2 x)
			(setq lst_design2
			       (gc:distinct (cons (fr:ReadDesign2 x) lst_design2))

			) ;_ setq
		   ) ;_ and
		 ) ;_ foreach
		 (and (fr:ReadDesign2 (fr:ReadDesignCalqueGC layname pos))
		      (setq lst_design2
			     (gc:distinct
			       (cons (fr:ReadDesign2 (fr:ReadDesignCalqueGC layname pos)) lst_design2)
			     ) ;_ gc:distinct

		      ) ;_ setq
		 ) ;_ and
	       ) ;_ if
	     ) ;_ progn
	) ;_ and
	(and (equal (type str-des1) 'STR)
	     (equal (substr str-des1 (strlen str-des1)) "*")
	     (equal (substr str-des1 1 (1- (strlen str-des1)))
		    (fr:ReadDesign1 (fr:ReadDesignCalqueGC layname 0) nil)
	     ) ;_ equal
	     (if (equal pos T)
	       (foreach	x (fr:ReadDesignCalqueGC layname nil)
		 (and (fr:ReadDesign2 x)
		      (setq lst_design2
			     (gc:distinct (cons (fr:ReadDesign2 x) lst_design2))

		      ) ;_ setq
		 ) ;_ and
	       ) ;_ foreach
	       (and (fr:ReadDesign2 (fr:ReadDesignCalqueGC layname pos))
		    (setq lst_design2
			   (gc:distinct
			     (cons (fr:ReadDesign2 (fr:ReadDesignCalqueGC layname pos)) lst_design2)
			   ) ;_ gc:distinct

		    ) ;_ setq
	       ) ;_ and
	     ) ;_ foreach
	) ;_ and
	(and (equal (type str-des1) 'STR)
	     (equal str-des1
		    (fr:ReadDesign1 (fr:ReadDesignCalqueGC layname 0) T)
	     ) ;_ equal
	     (if (equal pos T)
	       (foreach	x (fr:ReadDesignCalqueGC layname nil)
		 (and (fr:ReadDesign2 x)
		      (setq lst_design2
			     (gc:distinct (cons (fr:ReadDesign2 x) lst_design2))

		      ) ;_ setq
		 ) ;_ and
	       ) ;_ foreach
	       (and (fr:ReadDesign2 (fr:ReadDesignCalqueGC layname pos))
		    (setq lst_design2
			   (gc:distinct
			     (cons (fr:ReadDesign2 (fr:ReadDesignCalqueGC layname pos)) lst_design2)
			   ) ;_ gc:distinct

		    ) ;_ setq
	       ) ;_ and
	     ) ;_ foreach
	) ;_ and
    ) ;_ or
  ) ;_ vlax-for
  (if lst_design2
    lst_design2
    nil
  ) ;_ if
) ;_ defun




;;; routine fr:ReadListDesign1							;;;
;;; retourne  une list avec les différentes désignation 1 d'un jeu de selection	;;;
;;; argument:	ss	Jeu de selection					;;;
;;;		Pos   	0 pour un système (Par default)				;;;
;;; 			1 pour un type de système				;;;
;;; 			2 pour un élément de système				;;;
;;;										;;;

(defun fr:ReadListDesign1 (ss pos / lst-syst)
  (or pos (setq pos 0))
  (repeat (setq n (sslength ss))
    (setq ent	   (ssname ss (1- n))
	  str-syst (fr:ReadDesign1 (nth pos (fr:ReadDesignCalqueGC ent nil)) T)
    )
    (if	(distof (substr str-syst (strlen str-syst)))
      (progn
	(setq
	  lst-syst (gc:distinct
		     (cons str-syst lst-syst)
		   )
	  lst-syst (gc:distinct
		     (cons
		       (strcat
			 (substr str-syst 1 (- (strlen str-syst) 2))
			 "*"
		       )
		       lst-syst
		     )
		   )
	)
      )
      (setq lst-syst (gc:distinct (cons str-syst lst-syst))
      )
    )
    (setq n (1- n))
  )
  (if (= (length lst-syst) 2)
    (foreach x lst-syst
      (if (equal (substr x (strlen x)) "*")
	(setq lst-syst (vl-remove x lst-syst))
      )
    )
  )
  lst-syst
) ;defun


;;;										;;;
;;;										;;;
;;;										;;;
;;; argument: 	entitée sous forme <Nom d'entité: ID> (setq x (car(entsel)))	;;;
;;;		Pos   	0 pour un système 					;;;
;;; 			1 pour un type de système				;;;
;;; 			2 pour un élément de système				;;;
;;;		Si chaine de caractère Remplace par la chaine			;;;
;;;		Si T garde l'existant						;;;
;;;		Si nil suprime l'existant					;;;

(defun fr:WriteDesignCalqueGC
       (x pos chx-des1 chx-des2 / layname lst-deslay lst-lst-deslay)
  (setq	layname	       (vla-get-layer (vlax-ename->vla-object x))
	lst-lst-deslay (fr:ReadDesignCalqueGC x nil)
	lst-deslay (fr:ReadDesignCalqueGC x pos)
  )
  (or (equal chx-des1 T)
      (and (equal chx-des1 nil)
	   (setq lst-deslay
		  (gc:SubstAt
		    nil
		    0
		    lst-deslay
		  )
	   )
      )
      (and
	(equal (type chx-des1) 'STR)
	(setq lst-deslay
	       (gc:SubstAt
		 chx-des1
		 0
		 lst-deslay
	       )
	)
      )
  )
  (or (equal chx-des2 T)
      (and (equal chx-des2 nil)
	   (setq lst-deslay
		  (gc:SubstAt
		    nil
		    1
		    lst-deslay
		  )
	   )
      )
      (and
	(equal (type chx-des2) 'STR)
	(setq lst-deslay
	       (gc:SubstAt
		 chx-des2
		 1
		 lst-deslay
	       )
	)
      )
  )
  (setq	lst-lst-deslay
	 (gc:SubstAt
	   lst-deslay
	   pos
	   lst-lst-deslay
	 )
  )  
) ;defun

(defun fr:writeNwLayer2Lst (lst ent /)
  (setq	lst-layname (gc:str2lst (vla-get-layer (vlax-ename->vla-object ent)) " ")
    	lst-str nil
	nw-layname
	 (gc:lst2str
	   (gc:insertRange
	     (reverse (progn (foreach y	lst ;_ fr:WriteDesignCalqueGC
			       (if (nth 0 y)
				 (setq lst-str
					(cons (if (nth 1 y)
						(strcat (nth 0 y) "_" (nth 1 y)) ;_ strcat
						(nth 0 y)
					      ) ;_ if
					      lst-str
					) ;_ cons
				 ) ;_ setq
			       ) ;_ if
			     ) ;_ foreach
			     lst-str
		      ) ;_ progn
	     ) ;_ reverse
	     (1+ (vl-position "-" lst-layname))
	     (gc:removeRange
	       (1+ (vl-position "-" lst-layname))
	       (- (1- (length lst-layname))
		  (1+ (vl-position "-" lst-layname)) ;_ 1+
	       ) ;_ -
	       lst-layname
	     ) ;_ gc:removeRange
	   ) ;_ gc:insertRange
	   " "
	 ) ;_ gc:lst2str
  ) ;_ setq
) ;_ defun
